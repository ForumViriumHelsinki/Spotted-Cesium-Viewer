FME workspace spotted_ndvi_raster_range.fmw

Parameters:
- SourceDataset_TIFF_3 = /Users/andreas.andra/Downloads/ndvi_layer_2023_08_15_4326.tif   # Source TIFF (Tagged Image File Format) File(s)
- SourceDataset_WFS = https://kartta.hel.fi/ws/geoserver/avoindata/wfs   # Source WFS (Web Feature Service) URL
- DestDataset_POSTGRES = FVH   # Connection
- SourceDataset_WFS_3 = https://kartta.hel.fi/ws/geoserver/avoindata/wfs   # Source WFS (Web Feature Service) URL

Readers:
- TIFF_2: TIFF from $(SourceDataset_TIFF_3)
- WFS_1: WFS from $(SourceDataset_WFS)
- WFS_2: WFS from $(SourceDataset_WFS_3)

Writers:
- POSTGRES_1: POSTGRES to $(DestDataset_POSTGRES)

Piirijako_suurpiiri (reader WFS_1)
    attributes: gml_parent_id xml_buffer, gml_parent_property xml_buffer, gml_id xml_buffer, id xml_int32, aluejako xml_buffer, aluejako.xsi_nil xml_boolean, kunta xml_buffer, kunta.xsi_nil xml_boolean, tunnus xml_buffer, tunnus.xsi_nil xml_boolean, nimi_fi xml_buffer, nimi_fi.xsi_nil xml_boolean, nimi_se xml_buffer, nimi_se.xsi_nil xml_boolean, yhtluontipvm xml_date, yhtluontipvm.xsi_nil xml_boolean, yhtmuokkauspvm xml_date, yhtmuokkauspvm.xsi_nil xml_boolean, yhtdatanomistaja xml_buffer, yhtdatanomistaja.xsi_nil xml_boolean, kokotunnus xml_buffer, kokotunnus.xsi_nil xml_boolean, paivitetty_tietopalveluun xml_date, paivitetty_tietopalveluun.xsi_nil xml_boolean, datanomistaja xml_buffer, datanomistaja.xsi_nil xml_boolean, geom xml_geometry
    -> CoordinateSwapper
CoordinateSwapper
    SWAP_TYPE = X <-> Y
    -> Reprojector
Reprojector
    DEST = LL-WGS84
    INTERPOLATION_TYPE_NAME = Nearest Neighbor
    RASTER_CELL_SIZE = Preserve Cells
    RASTER_TOLERANCE = 0.0
    REPROJECTED -> SpatialFilter [Filter]
    REPROJECTED -> Clipper [CLIPPER]
TIFF (reader TIFF_2)
    -> Clipper [CANDIDATE]
Clipper
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    INSIDE -> AttributeRemover_2
AttributeRemover_2
    REMOVE_ATTRS = _clipped
    -> RasterToPolygonCoercer_2
RasterToPolygonCoercer_2
    EXTRACT_NODATA = No
    LABEL_ATTRIBUTE = _label
    PRESERVE_ATTRIBUTES = Yes
    POLYGONS -> Tester
Tester
    BOOL_OP = OR
    TEST_CLAUSE = TEST @Value(_label) >= 0
    TEST_MODE = TEST
    PASSED -> SpatialFilter [Candidate]
    FAILED -> Clipper_2 [CANDIDATE]
SpatialFilter
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    PASSED -> AttributeManager
Maavesi_suurpiirit (reader WFS_2)
    attributes: gml_parent_id xml_buffer, gml_parent_property xml_buffer, gml_id xml_buffer, tietopalvelu_id xml_int32, aluejako xml_buffer, aluejako.xsi_nil xml_boolean, tunnus xml_buffer, tunnus.xsi_nil xml_boolean, nimi_fi xml_buffer, nimi_fi.xsi_nil xml_boolean, nimi_se xml_buffer, nimi_se.xsi_nil xml_boolean, tyyppi xml_buffer, tyyppi.xsi_nil xml_boolean, pa xml_real32, pa.xsi_nil xml_boolean, paivitetty_tietopalveluun xml_date, paivitetty_tietopalveluun.xsi_nil xml_boolean, geom xml_geometry
    -> CoordinateSwapper_2
CoordinateSwapper_2
    SWAP_TYPE = X <-> Y
    -> Reprojector_2
Reprojector_2
    DEST = LL-WGS84
    INTERPOLATION_TYPE_NAME = Nearest Neighbor
    RASTER_CELL_SIZE = Preserve Cells
    RASTER_TOLERANCE = 0.0
    REPROJECTED -> SpatialFilter_2 [Filter]
    REPROJECTED -> Clipper_2 [CLIPPER]
Clipper_2
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    INSIDE -> Tester_2
Tester_2
    BOOL_OP = OR
    TEST_CLAUSE = TEST @Value(_clipped) = no
    TEST_MODE = TEST
    PASSED -> AttributeRemover_3
AttributeRemover_3
    REMOVE_ATTRS = _clipped
    -> SpatialFilter_2 [Candidate]
SpatialFilter_2
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    PASSED -> AttributeManager
AttributeManager
    ATTR_TABLE = SET_TO category = FME_CONDITIONAL:DEFAULT_VALUE'_FME_NO_OP_'BOOL_OP;OR;COMPOSITE_TEST;1;TEST @Value(_label) >= 0.6'very high'BOOL_OP;OR;COMPOSITE_TEST;1;TEST @Value(_label) >= 0.45'high'BOOL_OP;OR;COMPOSITE_TEST;1;TEST @Value(_label) >= 0.3'moderate'BOOL_OP;OR;COMPOSITE_TEST;1;TEST @Value(_label) >= 0.15'low'BOOL_OP;OR;COMPOSITE_TEST;1;TEST @Value(_label) >= 0'very low'FME_NUM_CONDITIONS6___
    USER_EXPOSED_ATTRIBUTES = index
    -> AttributeRemover
AttributeRemover
    REMOVE_ATTRS = _predicate,aluejako,datanomistaja,fme_basename,gml_id,gml_parent_id,gml_parent_property,id,kokotunnus,kunta,nimi_fi,nimi_se,paivitetty_tietopalveluun,yhtdatanomistaja,yhtluontipvm,yhtmuokkauspvm,_label,geom,pa,tietopalvelu_id,tyyppi
    -> Dissolver
Dissolver
    ACCUM_INPUT_ATTRS = Use Attributes From One Feature
    CLEANING_TOLERANCE = Automatic
    CONNECT_Z_MODE = First Wins
    DEAGGREGATE_INPUT = Yes
    GROUP_BY = category tunnus
    AREA -> GeometryExtractor
GeometryExtractor
    ATTR = location
    JSON_MAX_DIGITS = 7
    KIND_LONG = GeoJSON
    REMOVE_GEOMETRY = Yes
    -> spotted_helsinki_ndvi_range (writer POSTGRES_1)
spotted_helsinki_ndvi_range (writer POSTGRES_1)
    attributes: tunnus int4, category varchar(200), area_m2 float8, location text
