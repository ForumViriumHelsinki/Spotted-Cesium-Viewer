FME workspace ndvi_ylre_green_area_spotted.fmw

Parameters:
- SourceDataset_GEOJSON = /Users/andreas.andra/FME output/Spotted/ylre_viheralue.geojson   # Source GeoJSON File or URL
- SourceDataset_TIFF = /Users/andreas.andra/Downloads/ndvi_layer_2023_08_15_4326.tif   # Source TIFF (Tagged Image File Format) File(s)
- DestDataset_GEOJSON = /Users/andreas.andra/FME output/Spotted/ylre_with_ndvi.geojson   # Destination GeoJSON File

Readers:
- GEOJSON_1: GEOJSON from $(SourceDataset_GEOJSON)
- TIFF_1: TIFF from $(SourceDataset_TIFF)

Writers:
- GEOJSON_2: GEOJSON to $(DestDataset_GEOJSON)

YLRE_Viheralue_alue (reader GEOJSON_1)
    attributes: viheralue_id int, puistonumero int, puistonimi_id int, puiston_nimi string, osoite string, kaavamerkinta string, kaavamerkinta_teksti string, luokka string, kayttotark_id int, kayttotarkoitus string, omistaja string, rakentamisen_tila string, kaupunginosa string, osa_alue string, suurpiiri string, viheralueen_pa float, alue_luonti_pvm string, paivitetty_pvm string, datanomistaja string, vuokraus string, vuokraaja string
    -> Clipper [CLIPPER]
    -> SpatialFilter [Filter]
    -> FeatureMerger [REQUESTOR]
    -> FeatureMerger_2 [REQUESTOR]
TIFF (reader TIFF_1)
    -> Clipper [CANDIDATE]
Clipper
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    INSIDE -> AttributeRemover
AttributeRemover
    REMOVE_ATTRS = _clipped,fme_basename
    -> RasterToPolygonCoercer
RasterToPolygonCoercer
    EXTRACT_NODATA = No
    LABEL_ATTRIBUTE = _label
    PRESERVE_ATTRIBUTES = Yes
    POLYGONS -> SpatialFilter [Candidate]
    POLYGONS -> SpatialFilter_2 [Candidate]
SpatialFilter
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS WITHIN CONTAINS TOUCHES
    USE_BOUNDING_BOX = No
    PASSED -> StatisticsCalculator
StatisticsCalculator
    CALCULATION_MODE = NUMERIC
    FEAT_STATS = _label,NUMERIC_MODE,MIN,MAX,COUNT,,MEAN,MEDIAN,,,,,,,
    GROUP_BY = viheralue_id
    SUMMARY -> FeatureMerger [SUPPLIER]
FeatureMerger
    ATTR_ACCUM_MODE = Merge Supplier
    ATTR_CONFLICT_RES = Use Requestor
    IGNORE_NULLS = No
    JOIN_KEYS = @Value(viheralue_id) @Value(viheralue_id) AUTO
    MERGE_TYPE = Attributes Only
    PROCESS_DUPS = NO
    REJECT_NULL_MISSING_KEYS = No
    SUPPLIERS_FIRST = No
    MERGED -> AttributeRenamer
    UNMERGED_REQUESTOR -> SpatialFilter_2 [Filter]
SpatialFilter_2
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS WITHIN CONTAINS TOUCHES
    USE_BOUNDING_BOX = No
    PASSED -> StatisticsCalculator_2
StatisticsCalculator_2
    CALCULATION_MODE = NUMERIC
    FEAT_STATS = _label,NUMERIC_MODE,MIN,MAX,COUNT,,MEAN,MEDIAN,,,,,,,
    GROUP_BY = viheralue_id
    SUMMARY -> FeatureMerger_2 [SUPPLIER]
FeatureMerger_2
    ATTR_ACCUM_MODE = Merge Supplier
    ATTR_CONFLICT_RES = Use Requestor
    IGNORE_NULLS = No
    JOIN_KEYS = @Value(viheralue_id) @Value(viheralue_id) AUTO
    MERGE_TYPE = Attributes Only
    PROCESS_DUPS = NO
    REJECT_NULL_MISSING_KEYS = No
    SUPPLIERS_FIRST = No
    MERGED -> AttributeRenamer
AttributeRenamer
    ATTR_TABLE:
      RENAME_SET_DEFAULT _label.max > max_ndvi
      RENAME_SET_DEFAULT _label.min > min_ndvi
      RENAME_SET_DEFAULT _label.median > median_ndvi
      RENAME_SET_DEFAULT _label.mean > mean_ndvi
      RENAME_SET_DEFAULT _label.total_count > count_ndvi
    MISSING_INPUT_ATTRS = REMOVE
    -> YLRE_Viheralue_alue (writer GEOJSON_2)
YLRE_Viheralue_alue (writer GEOJSON_2)
    attributes: max_ndvi float, min_ndvi float, median_ndvi float, mean_ndvi float, count_ndvi string, viheralue_id int, puistonumero int, puistonimi_id int, puiston_nimi string, osoite string, kaavamerkinta string, kaavamerkinta_teksti string, luokka string, kayttotark_id int, kayttotarkoitus string, omistaja string, rakentamisen_tila string, kaupunginosa string, osa_alue string, suurpiiri string, viheralueen_pa float, alue_luonti_pvm string, paivitetty_pvm string, datanomistaja string, vuokraus string, vuokraaja string
