FME workspace geojson2postgis_ylre_spotted.fmw

Parameters:
- SourceDataset_GEOJSON = /Users/andreas.andra/FME output/Spotted/ylre_with_ndvi.geojson   # Source GeoJSON File or URL
- DestDataset_POSTGIS = FVH   # Connection

Readers:
- GEOJSON_1: GEOJSON from $(SourceDataset_GEOJSON)

Writers:
- POSTGIS_1: POSTGIS to $(DestDataset_POSTGIS)

YLRE_Viheralue_alue (reader GEOJSON_1)
    attributes: max_ndvi float, min_ndvi float, median_ndvi float, mean_ndvi float, count_ndvi string, viheralue_id int, puistonumero int, puistonimi_id int, puiston_nimi string, osoite string, kaavamerkinta string, kaavamerkinta_teksti string, luokka string, kayttotark_id int, kayttotarkoitus string, omistaja string, rakentamisen_tila string, kaupunginosa string, osa_alue string, suurpiiri string, viheralueen_pa float, alue_luonti_pvm string, paivitetty_pvm string, datanomistaja string, vuokraus string, vuokraaja string
    -> GeometryExtractor
GeometryExtractor
    ATTR = geom
    JSON_MAX_DIGITS = 7
    KIND_LONG = GeoJSON
    REMOVE_GEOMETRY = No
    -> ylre_viheralue_spotted (writer POSTGIS_1)
ylre_viheralue_spotted (writer POSTGIS_1)
    attributes: max_ndvi float8, min_ndvi float8, median_ndvi float8, mean_ndvi float8, count_ndvi text, viheralue_id int8, puistonumero int8, puistonimi_id int8, puiston_nimi text, osoite text, kaavamerkinta text, kaavamerkinta_teksti text, luokka text, kayttotark_id int8, kayttotarkoitus text, omistaja text, rakentamisen_tila text, kaupunginosa text, osa_alue text, suurpiiri text, viheralueen_pa float8, alue_luonti_pvm date, paivitetty_pvm date, datanomistaja text, vuokraus text, vuokraaja text, geom text
